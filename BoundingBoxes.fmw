FME workspace BoundingBoxes.fmw
Title: BoundingBoxes
Description: Berekent de bounding boxes voor de gemeente, gebieden en buurten uit de TIR en berekent aanvullende bounding boxes ten opzichte van een gegeven verhouding.
In de standaard situtaie worden bijpoorbeeld uitsnedes bepaalt zodat een gebied precies op A-standaard formaat past (A0, A3, A4, etc), zowel in portret- als in landschapsmodus.

Parameters:
- CANVASLANG = 1189   # Lange zijde canvas
- CANVASKORT = 841   # Korte zijde canvas
- BRON_TIR_GEMEENTE_SHP = K:\GEODATA\Basisdata\TIR\Data\SHP\Gemeente\Gemeente_vlakken.shp   # Source Esri Shapefile(s)
- BRON_TIR_GEBIEDEN_SHP = K:\GEODATA\Basisdata\TIR\Data\SHP\Gebieden\Gebieden_vlakken.shp   # Source Esri Shapefile(s)
- BRON_TIR_BUURTEN_SHP = K:\GEODATA\Basisdata\TIR\Data\SHP\Buurten\Buurten_vlakken.shp   # Source Esri Shapefile(s)
- DOEL_CSV = K:\GEODATA\Kennisloods\Data\BoundingBoxes\CSV   # Destination CSV (Comma Separated Value) Folder
- DOEL_SHP = K:\GEODATA\Kennisloods\Data\BoundingBoxes\SHP   # Destination Esri Shapefile Folder
- LOG_FILE = $(FME_MF_DIR)log\BoundingBoxes.log   # Log File

Readers:
- ESRISHAPE_1: ESRISHAPE from $(BRON_TIR_GEBIEDEN_SHP) in EPSG:28992
- ESRISHAPE_2: ESRISHAPE from $(BRON_TIR_GEMEENTE_SHP) in EPSG:28992
- ESRISHAPE_3: ESRISHAPE from $(BRON_TIR_BUURTEN_SHP) in EPSG:28992

Writers:
- CSV2_1: CSV2 to $(DOEL_CSV) in EPSG:28992
- ESRISHAPE_4: ESRISHAPE to $(DOEL_SHP) in EPSG:28992

Gemeente_vlakken (reader ESRISHAPE_2)
    attributes: GROEP char(9), KLASSE char(30), DGDT_ID long, CODE long, HERKOMST char(20), STATUS char(25), NIVO long, INWIN char(10), GEMEENTE long, GEBIED long, BUURT long, SUBBUURT long, SBTDEEL long, BLOK long, TEKST char(80), GEBDNAAM char(254), BUURTNAAM char(254), LAAG char(20)
    -> AttributeKeeper_GME
Gebieden_vlakken (reader ESRISHAPE_1)
    attributes: GROEP char(9), KLASSE char(30), DGDT_ID long, CODE long, HERKOMST char(20), STATUS char(25), NIVO long, INWIN char(10), GEMEENTE long, GEBIED long, BUURT long, SUBBUURT long, SBTDEEL long, BLOK long, TEKST char(80), GEBDNAAM char(254), BUURTNAAM char(254), LAAG char(20)
    -> AttributeKeeper_GBD
Buurten_vlakken (reader ESRISHAPE_3)
    attributes: GROEP char(9), KLASSE char(30), DGDT_ID long, CODE long, HERKOMST char(20), STATUS char(25), NIVO long, INWIN char(10), GEMEENTE long, GEBIED long, BUURT long, SUBBUURT long, SBTDEEL long, BLOK long, TEKST char(80), GEBDNAAM char(254), BUURTNAAM char(254), LAAG char(20)
    -> AttributeKeeper_BRT

Bookmark: voorbereiden invoer
AttributeKeeper_GME
    KEEP_ATTRS = GEMEENTE
    -> Counter
AttributeKeeper_GBD
    KEEP_ATTRS = GEBIED,GEBDNAAM,GEMEENTE
    -> Counter
AttributeKeeper_BRT
    KEEP_ATTRS = BUURT,GEBIED,GEBDNAAM,BUURTNAAM,GEMEENTE
    -> Counter
Counter
    CNT_ATTR = _dummyID
    START = 0
    SCOPE = Global
    DOMAIN = counter
    -> BoundsExtractor
    <REJECTED> -> _Rejected_

Bookmark: Boundingboxes berekenen
BoundsExtractor
    XMIN = _xmin
    XMAX = _xmax
    YMAX = _ymax
    YMIN = _ymin
    -> AttributeManager
AttributeManager
    ATTR_TABLE:
      SET_TO minX = @Evaluate(@floor(@Value(_xmin)))
      SET_TO minY = @Evaluate(@floor(@Value(_ymin)))
      SET_TO maxX = @Evaluate(@ceil(@Value(_xmax)))
      SET_TO maxY = @Evaluate(@ceil(@Value(_ymax)))
      REMOVE _xmax
      REMOVE _xmin
      REMOVE _ymax
      REMOVE _ymin
      SET_TO difX = @Evaluate(@Value(maxX)-@Value(minX))
      SET_TO difY = @Evaluate(@Value(maxY)-@Value(minY))
    -> AttributeCreator
AttributeCreator
    ATTR_TABLE:
      SET_TO _canvasVerhouding = @Evaluate($(CANVASKORT)/$(CANVASLANG))
      SET_TO _gebiedVerhouding = @Evaluate(@Value(difY)/@Value(difX))
      SET_TO _canvasVerhoudingPortret = @Evaluate(1/@Value(_canvasVerhouding))
    -> NieuweBoundsBerekenaar_landscape
    -> NieuweBoundsBerekenaar_Portret
    -> AttributeKeeper_BB
    -> AttributeManager_BB_geom
NieuweBoundsBerekenaar_landscape
    DIFY = @Value(difY)
    MAXX = @Value(maxX)
    _GEBIEDVERHOUDING = @Value(_gebiedVerhouding)
    MINX = @Value(minX)
    MINY = @Value(minY)
    DIFX = @Value(difX)
    _CANVASVERHOUDING = @Value(_canvasVerhouding)
    MAXY = @Value(maxY)
    -> AttributeManager_L
    -> AttributeManager_L_geom
    <Unfiltered> -> _Rejected_
NieuweBoundsBerekenaar_Portret
    DIFY = @Value(difY)
    MAXX = @Value(maxX)
    _GEBIEDVERHOUDING = @Value(_gebiedVerhouding)
    MINX = @Value(minX)
    MINY = @Value(minY)
    DIFX = @Value(difX)
    _CANVASVERHOUDING = @Value(_canvasVerhoudingPortret)
    MAXY = @Value(maxY)
    -> AttributeManager_P
    -> AttributeManager_P_geom
    <Unfiltered> -> _Rejected_

Bookmark: gegevens aggregeren naar gebied
AttributeKeeper_BB
    KEEP_ATTRS = BUURT,GEBIED,_dummyID,GEBDNAAM,BUURTNAAM,maxX,minX,minY,maxY,GEMEENTE
    -> FeatureMerger_BB_L [REQUESTOR]
AttributeManager_L
    ATTR_TABLE:
      REMOVE _canvasVerhouding
      REMOVE _gebiedVerhouding
      REMOVE difX
      REMOVE difY
      RENAME_SET_VALUE minX > landscape_minX
      RENAME_SET_VALUE maxX > landscape_maxX
      RENAME_SET_VALUE minY > landscape_minY
      RENAME_SET_VALUE maxY > landscape_maxY
      REMOVE _canvasVerhoudingPortret
      REMOVE GEBIED
      REMOVE GEBDNAAM
      REMOVE GEMEENTE
      REMOVE BUURT
      REMOVE BUURTNAAM
    -> FeatureMerger_BB_L [SUPPLIER]
FeatureMerger_BB_L
    PROCESS_DUPS = No
    ATTR_CONFLICT_RES = Use Requestor
    SUPPLIERS_FIRST = No
    REJECT_NULL_MISSING_KEYS = No
    JOIN_KEYS = @Value(_dummyID) @Value(_dummyID) AUTO
    IGNORE_NULLS = No
    MERGE_TYPE = Attributes Only
    ATTR_ACCUM_MODE = Merge Supplier
    MERGED -> FeatureMerger_BB_L_P [REQUESTOR]
    <REJECTED> -> _Rejected_
AttributeManager_P
    ATTR_TABLE:
      REMOVE _canvasVerhouding
      REMOVE _gebiedVerhouding
      REMOVE difX
      REMOVE difY
      RENAME_SET_VALUE minX > portrait_minX
      RENAME_SET_VALUE maxX > portrait_maxX
      RENAME_SET_VALUE minY > portrait_minY
      RENAME_SET_VALUE maxY > portrait_maxY
      REMOVE _canvasVerhoudingPortret
      REMOVE GEBIED
      REMOVE GEBDNAAM
      REMOVE GEMEENTE
      REMOVE BUURT
      REMOVE BUURTNAAM
    -> FeatureMerger_BB_L_P [SUPPLIER]
FeatureMerger_BB_L_P
    PROCESS_DUPS = No
    ATTR_CONFLICT_RES = Use Requestor
    SUPPLIERS_FIRST = No
    REJECT_NULL_MISSING_KEYS = No
    JOIN_KEYS = @Value(_dummyID) @Value(_dummyID) AUTO
    IGNORE_NULLS = No
    MERGE_TYPE = Attributes Only
    ATTR_ACCUM_MODE = Merge Supplier
    MERGED -> FeatureTypeFilter_Summary
    <REJECTED> -> _Rejected_

Bookmark: geometrie aanmaken
AttributeManager_L_geom
    ATTR_TABLE:
      REMOVE _dummyID
      REMOVE _canvasVerhouding
      REMOVE _gebiedVerhouding
      REMOVE _canvasVerhoudingPortret
      REMOVE difX
      REMOVE difY
    -> 2DBoxReplacer_L
2DBoxReplacer_L
    MINXVALATTR = @Value(minX)
    MAXYVALATTR = @Value(maxY)
    MAXXVALATTR = @Value(maxX)
    MINYVALATTR = @Value(minY)
    BOX -> FeatureTypeFilter_L
    <REJECTED> -> _Rejected_ [off]
AttributeManager_BB_geom
    ATTR_TABLE:
      REMOVE _dummyID
      REMOVE _canvasVerhouding
      REMOVE _gebiedVerhouding
      REMOVE _canvasVerhoudingPortret
      REMOVE difX
      REMOVE difY
    -> 2DBoxReplacer
2DBoxReplacer
    MINXVALATTR = @Value(minX)
    MAXYVALATTR = @Value(maxY)
    MAXXVALATTR = @Value(maxX)
    MINYVALATTR = @Value(minY)
    BOX -> FeatureTypeFilter_BB
    <REJECTED> -> _Rejected_
AttributeManager_P_geom
    ATTR_TABLE:
      REMOVE _dummyID
      REMOVE _canvasVerhouding
      REMOVE _gebiedVerhouding
      REMOVE _canvasVerhoudingPortret
      REMOVE difX
      REMOVE difY
    -> 2DBoxReplacer_P
2DBoxReplacer_P
    MINXVALATTR = @Value(minX)
    MAXYVALATTR = @Value(maxY)
    MAXXVALATTR = @Value(maxX)
    MINYVALATTR = @Value(minY)
    BOX -> FeatureTypeFilter_P
    <REJECTED> -> _Rejected_ [off]

Bookmark: uitvoeren
FeatureTypeFilter_L
    ATTRIBUTES = <Blank>,<Unfiltered>,Gemeente_vlakken,Gebieden_vlakken,Buurten_vlakken
    Gemeente_vlakken -> BoundingBoxLandscape_Gemeente (writer ESRISHAPE_4)
    Gebieden_vlakken -> BoundingBoxLandscape_Gebieden (writer ESRISHAPE_4)
    Buurten_vlakken -> BoundingBoxLandscape_Buurten (writer ESRISHAPE_4)
BoundingBoxLandscape_Gemeente (writer ESRISHAPE_4)
    attributes: GEMEENTE long, minX number(6,0), minY number(6,0), maxX number(6,0), maxY number(6,0)
BoundingBoxLandscape_Gebieden (writer ESRISHAPE_4)
    attributes: GEMEENTE long, GEBIED long, GEBDNAAM char(254), minX number(6,0), minY number(6,0), maxX number(6,0), maxY number(6,0)
BoundingBoxLandscape_Buurten (writer ESRISHAPE_4)
    attributes: GEMEENTE long, GEBIED long, GEBDNAAM char(254), BUURT long, BUURTNAAM char(254), minX number(6,0), minY number(6,0), maxX number(6,0), maxY number(6,0)
FeatureTypeFilter_BB
    ATTRIBUTES = <Blank>,<Unfiltered>,Gemeente_vlakken,Gebieden_vlakken,Buurten_vlakken
    Gemeente_vlakken -> BoundingBox_Gemeente (writer ESRISHAPE_4)
    Gebieden_vlakken -> BoundingBox_Gebieden (writer ESRISHAPE_4)
    Buurten_vlakken -> BoundingBox_Buurten (writer ESRISHAPE_4)
BoundingBox_Gemeente (writer ESRISHAPE_4)
    attributes: GEMEENTE long, minX number(6,0), minY number(6,0), maxX number(6,0), maxY number(6,0)
BoundingBox_Gebieden (writer ESRISHAPE_4)
    attributes: GEMEENTE long, GEBIED long, GEBDNAAM char(254), minX number(6,0), minY number(6,0), maxX number(6,0), maxY number(6,0)
BoundingBox_Buurten (writer ESRISHAPE_4)
    attributes: GEMEENTE long, GEBIED long, GEBDNAAM char(254), BUURT long, BUURTNAAM char(254), minX number(6,0), minY number(6,0), maxX number(6,0), maxY number(6,0)
FeatureTypeFilter_Summary
    ATTRIBUTES = <Blank>,<Unfiltered>,Gemeente_vlakken,Gebieden_vlakken,Buurten_vlakken
    Gemeente_vlakken -> AttributeKeeper_GME_CSV
    Gebieden_vlakken -> AttributeKeeper_GBD_CSV
    Buurten_vlakken -> AttributeKeeper_BRT_CSV
AttributeKeeper_GME_CSV
    KEEP_ATTRS = portrait_minX,landscape_minX,landscape_maxY,maxX,landscape_minY,minX,minY,maxY,portrait_maxX,portrait_minY,portrait_maxY,GEMEENTE,landscape_maxX
    -> BoundingBox_Gemeente (writer CSV2_1)
BoundingBox_Gemeente (writer CSV2_1)
    attributes: GEMEENTE string, minX int32, minY int32, maxX int32, maxY int32, landscape_minX int32, landscape_maxX int32, landscape_minY int32, landscape_maxY int32, portrait_minX int32, portrait_maxX int32, portrait_minY int32, portrait_maxY int32
AttributeKeeper_GBD_CSV
    KEEP_ATTRS = portrait_minX,landscape_minX,GEBIED,GEBDNAAM,landscape_maxY,maxX,landscape_minY,minX,minY,maxY,portrait_maxX,portrait_minY,portrait_maxY,GEMEENTE,landscape_maxX
    -> BoundingBox_Gebieden (writer CSV2_1)
BoundingBox_Gebieden (writer CSV2_1)
    attributes: GEMEENTE string, GEBIED int32, GEBDNAAM string, minX string, minY int32, maxX int32, maxY int32, landscape_minX int32, landscape_maxX int32, landscape_minY int32, landscape_maxY int32, portrait_minX int32, portrait_maxX int32, portrait_minY int32, portrait_maxY int32
AttributeKeeper_BRT_CSV
    KEEP_ATTRS = portrait_minX,BUURT,landscape_minX,GEBIED,GEBDNAAM,landscape_maxY,BUURTNAAM,maxX,landscape_minY,minX,minY,maxY,portrait_maxX,portrait_minY,portrait_maxY,GEMEENTE,landscape_maxX
    -> BoundingBox_Buurten (writer CSV2_1)
BoundingBox_Buurten (writer CSV2_1)
    attributes: GEMEENTE string, GEBIED int32, GEBDNAAM string, BUURT int32, BUURTNAAM string, minX int32, minY int32, maxX int32, maxY int32, landscape_minX int32, landscape_maxX int32, landscape_minY int32, landscape_maxY int32, portrait_minX int32, portrait_maxX int32, portrait_minY int32, portrait_maxY int32
FeatureTypeFilter_P
    ATTRIBUTES = <Blank>,<Unfiltered>,Gemeente_vlakken,Gebieden_vlakken,Buurten_vlakken
    Gemeente_vlakken -> BoundingBoxPortrait_Gemeente (writer ESRISHAPE_4)
    Gebieden_vlakken -> BoundingBoxPortrait_Gebieden (writer ESRISHAPE_4)
    Buurten_vlakken -> BoundingBoxPortrait_Buurten (writer ESRISHAPE_4)
BoundingBoxPortrait_Gemeente (writer ESRISHAPE_4)
    attributes: GEMEENTE long, minX number(6,0), minY number(6,0), maxX number(6,0), maxY number(6,0)
BoundingBoxPortrait_Gebieden (writer ESRISHAPE_4)
    attributes: GEMEENTE long, GEBIED long, GEBDNAAM char(254), minX number(6,0), minY number(6,0), maxX number(6,0), maxY number(6,0)
BoundingBoxPortrait_Buurten (writer ESRISHAPE_4)
    attributes: GEMEENTE long, GEBIED long, GEBDNAAM char(254), BUURT long, BUURTNAAM char(254), minX number(6,0), minY number(6,0), maxX number(6,0), maxY number(6,0)

Bookmark: uitval
_Rejected_: Logger
    MESSAGE = Feature is:
    MAXFEATS = 20
    MAXCOORDS = 20

FME custom transformer NieuweBoundsBerekenaar
Berekent nieuwe boundingboxes zodat deze dezelfde verhouding hebben als het canvas.

Parameters:
- _GEBIEDVERHOUDING = @Value(_gebiedVerhouding)   # Gebiedverhouding
- _CANVASVERHOUDING = @Value(_canvasVerhouding)   # Canvasverhouding
- MAXX = @Value(maxX)   # maxX
- MINX = @Value(minX)   # minX
- DIFX = @Value(difX)   # difX
- MINY = @Value(minY)   # minY
- MAXY = @Value(maxY)   # maxY
- DIFY = @Value(difY)   # difY

Input (input)
    -> TestFilter
TestFilter
    TEST_LIST = BOOL_OP,OR,COMPOSITE_TEST,<Unused>,TEST_CLAUSE,"TEST @Value(_canvasVerhouding) = @Value(_gebiedVerhouding)",verhouding Canvas = verhouding Gebied,BOOL_OP,OR,COMPOSITE_TEST,<Unused>,TEST_CLAUSE,"TEST @Value(_canvasVerhouding) < @Value(_gebiedVerhouding)",verhouding Canvas < verhouding Gebied,BOOL_OP,OR,COMPOSITE_TEST,<Unused>,TEST_CLAUSE,"TEST @Value(_canvasVerhouding) > @Value(_gebiedVerhouding)",verhouding Canvas > verhouding Gebied
    DEFAULT_VALUE = <UNFILTERED>
    verhouding Canvas = verhouding Gebied -> deltas0
    verhouding Canvas < verhouding Gebied -> deltaX
    verhouding Canvas > verhouding Gebied -> deltaY
    <UNFILTERED> -> <Unfiltered> (output)
deltas0: AttributeCreator
    ATTR_TABLE:
      SET_TO minXnieuw = @Value(minX)
      SET_TO minYnieuw = @Value(minY)
      SET_TO maxXnieuw = @Value(maxX)
      SET_TO maxYnieuw = @Value(maxY)
    -> AttributeManager_2
deltaX: AttributeCreator
    ATTR_TABLE:
      SET_TO deltaX = @Evaluate((@Value(difY)/@Value(_canvasVerhouding))-@Value(difX))
      SET_TO minXnieuw = @Evaluate(@floor(@Value(minX)-(@Value(deltaX)/2)))
      SET_TO minYnieuw = @Value(minY)
      SET_TO maxXnieuw = @Evaluate(@ceil(@Value(maxX)+(@Value(deltaX)/2)))
      SET_TO maxYnieuw = @Value(maxY)
    -> AttributeManager_2
deltaY: AttributeCreator
    ATTR_TABLE:
      SET_TO deltaY = @Evaluate((@Value(difX)*@Value(_canvasVerhouding))-@Value(difY))
      SET_TO minXnieuw = @Value(minX)
      SET_TO minYnieuw = @Evaluate(@floor(@Value(minY)-(@Value(deltaY)/2)))
      SET_TO maxXnieuw = @Value(maxX)
      SET_TO maxYnieuw = @Evaluate(@ceil(@Value(maxY)+(@Value(deltaY)/2)))
    -> AttributeManager_2
AttributeManager_2
    ATTR_TABLE:
      REMOVE minX
      REMOVE minY
      REMOVE maxX
      REMOVE maxY
      REMOVE deltaX
      RENAME_SET_VALUE minXnieuw > minX
      RENAME_SET_VALUE maxXnieuw > maxX
      REMOVE deltaY
      RENAME_SET_VALUE minYnieuw > minY
      RENAME_SET_VALUE maxYnieuw > maxY
    -> Output (output)
Output (output)
<Unfiltered> (output)
